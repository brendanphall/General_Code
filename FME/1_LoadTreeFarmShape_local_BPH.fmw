FME workspace 1_LoadTreeFarmShape_local_BPH.fmw

Parameters:
- DestDataset_MDB_ADO =
- SourceDataset_MSSQL_ADO =
- SourceDataset_MSSQL_SPATIAL =
- SourceDataset_SHAPEFILE =
- tfstate =

Readers:
- MSSQL_ADO_1: MSSQL_ADO from $(SourceDataset_MSSQL_ADO)
- MSSQL_SPATIAL_1: MSSQL_SPATIAL from $(SourceDataset_MSSQL_SPATIAL)
- SHAPEFILE_2: SHAPEFILE from $(SourceDataset_SHAPEFILE)

Writers:
- MDB_ADO_1: MDB_ADO to $(DestDataset_MDB_ADO)

MD_TreeFarm_ForUpload (reader SHAPEFILE_2)
    attributes: Location varchar(254), State varchar(2), TreeFarmID varchar(10), Shape_Leng double, Shape_Area double
    -> AttributeCreator
AttributeCreator
    ATTR_TABLE:
      SET_TO TF_State = XX
      SET_TO TreeFarmNumber = @Trim(@Value(TreeFarmID))
      SET_TO totalforestedacres = 0
    -> FeatureMerger [REQUESTOR]
treefarm (reader MSSQL_ADO_1)
    attributes: treefarm_id identity, state char(2), treefarmnumber varchar(32), treefarmname varchar(64), treefarmtype varchar(64), totalacres float, treefarmstatus varchar(64), certdecertdate datetime, decertificationreason varchar(64), lastinspection_id integer, initialinspectiondate datetime, initialcertificationdate datetime, treefarmcreatedatetime datetime, treefarmcreatedbyperson_id integer, treefarmmodifieddatetime datetime, treefarmmodifiedbyperson_id integer, group_id integer, thirdpartycert_id integer, ownershiptype varchar(64), isactionitem varchar(1), treefarmnotes varchar(2047)
    -> AttributeCreator_3
AttributeCreator_3
    ATTR_TABLE = SET_TO TreeFarmNumber = @Value(treefarmnumber)
    -> FeatureMerger [SUPPLIER]
FeatureMerger
    ATTR_ACCUM_MODE = Merge Supplier
    ATTR_CONFLICT_RES = Use Requestor
    IGNORE_NULLS = No
    JOIN_KEYS = @Value(TreeFarmNumber) @Value(TreeFarmNumber) STRING
    MERGE_TYPE = Attributes Only
    PROCESS_DUPS = NO
    REJECT_NULL_MISSING_KEYS = No
    SUPPLIERS_FIRST = No
    MERGED -> Sorter
    UNMERGED_REQUESTOR -> NotFound (writer MDB_ADO_1)
    <REJECTED> -> treefarm (writer MDB_ADO_1)
Sorter
    SORT_PARM = treefarm_id NUMERIC ASCENDING
    SORTED -> DuplicateFilter
DuplicateFilter
    INPUT_ORDERED_CHOICE = Yes
    KEYATTR = treefarm_id
    UNIQUE -> FeatureJoiner [LEFT]
    DUPLICATE -> duplicate (writer MDB_ADO_1)
duplicate (writer MDB_ADO_1)
    attributes: state text(15), treefarmnumber text(32), Acres single, ForestedAc single
NotFound (writer MDB_ADO_1)
    attributes: STATE text(5), TREEFARMNUMBER text(32)
treefarm (writer MDB_ADO_1)
    attributes: treefarm_id long, state text(2), treefarmnumber text(32), treefarmname text(64), treefarmtype text(64), totalacres double, treefarmstatus text(64), certdecertdate datetime, decertificationreason text(64), lastinspection_id long, initialinspectiondate datetime, initialcertificationdate datetime, treefarmcreatedatetime datetime, treefarmcreatedbyperson_id long, treefarmmodifieddatetime datetime, treefarmmodifiedbyperson_id long, group_id long, thirdpartycert_id long, ownershiptype text(64), isactionitem text(1), treefarmnotes text(255)
TREEFARM (reader MSSQL_SPATIAL_1)
    attributes: OBJECTID integer, treefarm_id integer, parcelnumber smallint
    -> FeatureJoiner [RIGHT]
FeatureJoiner
    ATTR_CONFLICT_RES = Use Left
    GEOMETRY_HANDLING = Use Left
    JOIN_KEYS = treefarm_id treefarm_id AUTO
    JOIN_MODE = Inner
    JOINED -> geomexists (writer MDB_ADO_1)
    UNJOINED_LEFT -> AttributeCreator_2
geomexists (writer MDB_ADO_1)
    attributes: treefarm_id text(20), STATE text(5), TREEFARMNUMBER text(32)
AttributeCreator_2
    ATTR_TABLE = SET_TO parcelnumber = 1
    -> tmp_treefarm (writer MDB_ADO_1)
tmp_treefarm (writer MDB_ADO_1)
    attributes: treefarm_id long, parcelnumber long, totalforestedacres single
