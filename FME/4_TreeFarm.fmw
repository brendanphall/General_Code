FME workspace 4_TreeFarm.fmw

Parameters:
- DestDataset_GEODATABASE_FILE = $(FME_MF_DIR)atfs_update.gdb   # File Geodatabase
- SourceDataset_MSSQL_ADO = prod-atfs-db   # SQL Server Connection
- tfstate = KY   # Tree Farm State
- SourceDataset_SHAPEFILE_3 = $(FME_MF_DIR)shapefile\To_AFF_3-19-25_partial.shp   # Source Esri Shapefile(s)

Readers:
- MSSQL_ADO_1: MSSQL_ADO from $(SourceDataset_MSSQL_ADO)
- SHAPEFILE_1: SHAPEFILE from $(SourceDataset_SHAPEFILE_3)

Writers:
- GEODATABASE_FILE_1: GEODATABASE_FILE to $(DestDataset_GEODATABASE_FILE)

To_AFF_3-19-25_partial (reader SHAPEFILE_1)
    attributes: ID long, ACRES double, OWNER char(16), Number char(10)
    -> Tester
Tester
    BOOL_OP = OR
    COMPOSITE_TEST = 1
    TEST_CLAUSE = TEST @Value(Number) NOT_IN 'GF-8257','GF-8337'
    TEST_MODE = TEST
    PASSED -> AttributeCreator
AttributeCreator
    ATTR_TABLE:
      SET_TO TF_State = XX
      SET_TO TreeFarmNumber = @Trim(@Value(Number))
      SET_TO totalforestedacres = @Value(ACRES)
    -> FeatureMerger [REQUESTOR]
treefarm (reader MSSQL_ADO_1)
    attributes: treefarm_id identity, state char(2), treefarmnumber varchar(32), treefarmname varchar(64), treefarmtype varchar(64), totalacres float, treefarmstatus varchar(64), certdecertdate datetime, decertificationreason varchar(64), lastinspection_id integer, initialinspectiondate datetime, initialcertificationdate datetime, treefarmcreatedatetime datetime, treefarmcreatedbyperson_id integer, treefarmmodifieddatetime datetime, treefarmmodifiedbyperson_id integer, group_id integer, thirdpartycert_id integer, ownershiptype varchar(64), isactionitem varchar(1), treefarmnotes varchar(2047)
    -> AttributeCreator_4
AttributeCreator_4
    ATTR_TABLE = SET_TO TreeFarmNumber = @Value(treefarmnumber)
    -> FeatureMerger [SUPPLIER]
FeatureMerger
    ATTR_ACCUM_MODE = Merge Supplier
    ATTR_CONFLICT_RES = Use Requestor
    IGNORE_NULLS = No
    JOIN_KEYS = @Value(TreeFarmNumber) @Value(TreeFarmNumber) STRING
    MERGE_TYPE = Attributes Only
    PROCESS_DUPS = NO
    REJECT_NULL_MISSING_KEYS = No
    SUPPLIERS_FIRST = No
    MERGED -> Sorter
Sorter
    SORT_PARM = treefarm_id NUMERIC ASCENDING
    SORTED -> DuplicateFilter
DuplicateFilter
    INPUT_ORDERED_CHOICE = Yes
    KEYATTR = treefarm_id
    UNIQUE -> EsriReprojector_2
EsriReprojector_2
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_DIRECTION = Reverse
    GEOTRANSFORMATION_NAME = WGS_1984_(ITRF00)_To_NAD_1983
    INTERPOLATION_TYPE_NAME = Nearest Neighbor
    RASTER_CELL_SIZE = Preserve Cells
    RASTER_TOLERANCE = 0.0
    SOURCE = ESRIWKT|NAD_1983_Michigan_GeoRef_Meters|PROJCS["NAD_1983_Michigan_GeoRef_Meters",GEOGCS["GCS_North_American_1983",DATUM["D_North_American_1983",SPHEROID["GRS_1980",6378137.0,298.257222101]],PRIMEM["Greenwich",0.0],UNIT["Degree",0.0174532925199433]],PROJECTION["Hotine_Oblique_Mercator_Azimuth_Natural_Origin"],PARAMETER["False_Easting",2546731.496],PARAMETER["False_Northing",-4354009.816],PARAMETER["Scale_Factor",0.9996],PARAMETER["Azimuth",337.25556],PARAMETER["Longitude_Of_Center",-86.0],PARAMETER["Latitude_Of_Center",45.30916666666666],UNIT["Meter",1.0]]
    REPROJECTED -> AttributeCreator_2
AttributeCreator_2
    ATTR_TABLE = SET_TO parcelnumber = 1
    -> tmp_treefarm (writer GEODATABASE_FILE_1)
tmp_treefarm (writer GEODATABASE_FILE_1)
    attributes: treefarm_id integer, parcelnumber smallint, totalacres float, totalforestedacres float, longitude char(20), latitude char(20), dlongitude double, dlatitude double
